"""Show the full v33 cat, without altering or saving the signed CAD source."""
from pathlib import Path
import json
import FreeCAD as A
import FreeCADGui as G
root=Path(__file__).resolve().parents[3]; folder=root/'hardware/skorupa/v33'
plan=json.loads((folder/'assembly-plan.json').read_text()); path=folder/plan['cad_filename']
d=next((o for o in A.listDocuments().values() if o.FileName and Path(o.FileName).resolve()==path.resolve()),None)
if d is None:d=A.openDocument(str(path))
A.setActiveDocument(d.Name)
for r in plan['components']:d.getObject(r['name']).Visibility=True
d.getObject('HeadFront').ViewObject.Transparency=0
G.Selection.clearSelection();v=G.activeDocument().activeView();v.setCameraType('Orthographic')
direction=A.Vector(-1,-1,.7)
v.setCameraOrientation(A.Rotation(A.Vector(0,0,1).cross(direction),A.Vector(0,0,1),direction,'ZXY').Q)
v.fitAll();G.updateGui()
print('Whole v33 shown; signed file unchanged')

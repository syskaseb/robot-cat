"""Native 13-axis connection test and exact saved world shapes for v31."""
from pathlib import Path
import hashlib,json,math,sys
import FreeCAD as A,FreeCADGui as G
ROOT=Path(__file__).resolve().parents[3];OUT=ROOT/'hardware/skorupa/v31'
target=OUT/'Kot_v31_ZASILANIE.FCStd'
d=next(x for x in A.listDocuments().values() if x.FileName and Path(x.FileName).resolve()==target.resolve())
asm=d.getObject('RobotCatAssembly24');plan=json.loads((OUT/'assembly-plan.json').read_text())
assert hashlib.sha256((OUT/'PowerDesign31.FCStd').read_bytes()).hexdigest()==plan['master_sha256']
sys.path.insert(0,A.getHomePath()+'Mod/Assembly')
import CommandCreateSimulation as CS,UtilsAssembly
sim=d.getObject('RobotConnectionTest31')
if sim is None:
    sim=UtilsAssembly.getSimulationGroup(asm).newObject('App::FeaturePython','RobotConnectionTest31')
    CS.Simulation(sim);CS.ViewProviderSimulation(sim.ViewObject);motions=[]
    for row in plan['joints']:
        if row['type']!='Revolute':continue
        motion=asm.newObject('App::FeaturePython','Combined31_'+row['name'])
        formula='0.523598775598299*sin(2*pi*time)' if row['name']=='Rev_TailYaw29' else d.getObject('Motion_'+row['name']).Formula
        CS.Motion(motion,'Angular',(d.getObject(row['name']),['']),formula)
        CS.ViewProviderMotion(motion.ViewObject);motions.append(motion)
    sim.Group=motions
sim.Label='v31 | lapy +/-3deg, ogon +/-30deg | IMU i Pololu przy ramie'
sim.aTimeStart=0;sim.bTimeEnd=1;sim.cTimeStepOutput=.05;sim.jFramesPerSecond=20
d.recompute()
baseline={r['name']:d.getObject('Rigid_'+r['name']).Placement.copy() for r in plan['components']}
assert all(p.isSame(A.Placement(),1e-6) for p in baseline.values())
rows=[];peaks={}
try:
    result=asm.generateSimulation(sim);assert asm.numberOfFrames()>=20
    for i in range(asm.numberOfFrames()):
        asm.updateForFrame(i);t=r=a=0.;angles={}
        for row in plan['joints']:
            j=d.getObject(row['name']);p=j.Reference1[0].Placement*j.Placement1;q=j.Reference2[0].Placement*j.Placement2
            t=max(t,(p.Base-q.Base).Length)
            theta=(p.Rotation.inverted()*q.Rotation).Angle
            if row['type']=='Fixed':r=max(r,theta)
            else:
                a=max(a,p.Rotation.multVec(A.Vector(0,0,1)).getAngle(q.Rotation.multVec(A.Vector(0,0,1))))
                angles[row['name']]=math.degrees(theta);peaks[row['name']]=max(peaks.get(row['name'],0),math.degrees(theta))
        assert max(t,r,a)<1e-5
        assert d.getObject('Rigid_IMU').Placement.isSame(baseline['IMU'],1e-6)
        assert d.getObject('Rigid_Pololu').Placement.isSame(baseline['Pololu'],1e-6)
        rows.append(dict(frame=i,max_joint_gap_mm=t,max_fixed_error_rad=r,max_axis_error_rad=a,angles_deg=angles,imu_fixed_to_chassis=True,power_fixed_to_chassis=True))
    assert abs(peaks['Rev_TailYaw29']-30)<1e-5
    assert all(abs(v-3)<1e-5 for n,v in peaks.items() if n!='Rev_TailYaw29')
finally:
    for n,p in baseline.items():d.getObject('Rigid_'+n).Placement=p
    d.recompute();assert asm.solve()==0
assert all(d.getObject('Rigid_'+n).Placement.isSame(p,1e-6) for n,p in baseline.items())
for row in plan['components']:
    o=d.getObject(row['name']);assert o.Shape.isValid() and o.Shape.Solids,row['name']
d.Label='Kot v31 - montaz glownego Pololu - PROTOTYP';d.recompute();d.save()
digest=hashlib.sha256(target.read_bytes()).hexdigest();plan['source_sha256']=digest
(OUT/'assembly-plan.json').write_text(json.dumps(plan,indent=2),encoding='utf8')
cache=OUT/'shape-cache';cache.mkdir(exist_ok=True)
for row in plan['components']:
    o=d.getObject(row['name']);s=o.Shape.copy();s.Placement=o.getGlobalPlacement()*o.Placement.inverse()*s.Placement
    s.exportBrep(str(cache/(o.Name+'.brep')))
(cache/'index.json').write_text(json.dumps(dict(source_sha256=digest,objects=[r['name'] for r in plan['components']]),indent=2),encoding='utf8')
report=dict(source_sha256=digest,master_sha256=plan['master_sha256'],components=len(plan['components']),fixed=plan['fixed_count'],revolute=plan['revolute_count'],temporary=plan['temporary_locks'],solver_result=0,restored=True,
    scope='Native connection retention and IMU/Pololu rigid-body ownership, not load, magnetic calibration or complete collision certification.',tests=[dict(simulation=sim.Name,frames=rows,peak_angles_deg=peaks)])
(OUT/'assembly-validation.json').write_text(json.dumps(report,indent=2),encoding='utf8')
A.setActiveDocument(d.Name);v=G.activeDocument().activeView();v.viewAxonometric();v.setCameraOrientation((A.Rotation(A.Vector(0,0,1),180)*v.getCameraOrientation()).Q);v.fitAll();G.updateGui()
print(json.dumps(dict(saved=d.FileName,frames=len(rows),components=report['components'],fixed=report['fixed'],revolute=report['revolute'],temporary=report['temporary'],imu_fixed_to_chassis=True,power_fixed_to_chassis=True)))

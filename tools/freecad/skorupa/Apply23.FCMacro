"""MCP imports validated world shapes into a new native checkpoint."""
from pathlib import Path
import json,hashlib,shutil
import FreeCAD as A,FreeCADGui as G
import Part
ROOT=Path(__file__).resolve().parents[3]; OUT=ROOT/'hardware/skorupa/v23'
SOURCE=ROOT/'hardware/skorupa/v22/Kot_v22_BRZUCH_PETG.FCStd'
DEST=OUT/'Kot_v23_AKUMULATOR_PETG.FCStd'
r=json.loads((OUT/'validation.json').read_text(encoding='utf-8'))
c=json.loads((OUT/'assembly-validation.json').read_text(encoding='utf-8'))
assert not r['collisions'] and not c['tool_collisions']
assert len(c['bearings'])==16 and all(t['material_fraction']>=.99 for t in c['bearings'])
assert len(c['nut_insertion'])==32 and all(t['overlap_mm3']<.001 for t in c['nut_insertion'])
assert len(c['belly_removal_samples'])==19 and all(not t['new_part_collisions'] for t in c['belly_removal_samples'])
assert hashlib.sha256(SOURCE.read_bytes()).hexdigest()==r['source_sha256']
for p in r['parts']+r['hardware']:
    assert hashlib.sha256((OUT/(p['name']+'.brep')).read_bytes()).hexdigest()==p['sha256']==c['source_breps'][p['name']]
if DEST.exists(): raise RuntimeError('Preserve existing v23')
shutil.copy2(SOURCE,DEST); d=A.openDocument(str(DEST))
d.Label='Kot v23 | mocowanie akumulatora PETG | PROTOTYP'
group=d.addObject('App::Part','BatteryAssembly23'); group.Label='Akumulator | tacka PETG, metal, miekka podkladka i paski'
for p in r['parts']+r['hardware']:
    name=p['name']; o=d.addObject('Part::Feature',name); group.addObject(o)
    s=Part.Shape(); s.read(str(OUT/(name+'.brep'))); o.Shape=s
    if name=='BatteryCarrier23': material='Black PETG prototype'; color=(.12,.13,.15)
    elif name=='BatteryLiner23': material='Bought 1 mm non-conductive soft liner, supplier TBD'; color=(.32,.32,.34)
    elif name.startswith('BatteryStrap'): material='Bought 15 mm hook-loop textile strap, dimensional envelope, supplier TBD'; color=(.07,.08,.09)
    else: material='Steel fastener envelope; no threads/socket'; color=(.6,.62,.65)
    o.Label=material.split(';')[0]+' | '+name
    o.addProperty('App::PropertyString','MaterialNote','Manufacturing').MaterialNote=material
    o.addProperty('App::PropertyString','SourceRecipe','Manufacturing').SourceRecipe='tools/freecad/skorupa/build23.py'
    o.ViewObject.ShapeColor=color; o.ViewObject.LineColor=(.04,.04,.05); o.ViewObject.DisplayMode='Flat Lines'; o.Visibility=True
d.getObject('BatteryTray').Visibility=False
o=d.getObject('BatteryCarrier23')
o.addProperty('App::PropertyString','Mounting','Manufacturing').Mounting='4 M2.5x8 ISO7380-1, head max D4.7 x H1.5; existing plate bores D2.6, carrier D2.9, captive nuts AF5 x H2 in AF5.3 slots. Preload nuts and straps before placing carrier.'
o.addProperty('App::PropertyString','PrototypeLimits','Manufacturing').PrototypeLimits='Confirm actual pack/cables, low-head clearance 0.5mm, legacy plate strength, strap retention and PETG bridges; battery service path not yet validated. Not Assembly solver joints.'
d.recompute(); A.setActiveDocument(d.Name)
view=G.getDocument(d.Name).activeView(); view.setAxisCross(False); view.setCameraType('Orthographic')
z=A.Vector(-1,-1,.65); x=A.Vector(1,-1,0)
G.updateGui()
if hasattr(G,'Snapper') and G.Snapper.grid: G.Snapper.grid.off()
view.setCameraOrientation(A.Rotation(x,z.cross(x),z,'ZXY').Q); view.fitAll()
node=view.getCameraNode(); node.height.setValue(node.height.getValue()*.6)
G.updateGui(); view.redraw(); d.save()
view.saveImage(str(OUT/'kot-v23-zlozony.png'),1400,1050,'White')
print('Saved',d.FileName)
